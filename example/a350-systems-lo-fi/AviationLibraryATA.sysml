library package AviationLibraryATA {
    part def Aircraft;
    
    part def AircraftSystem;
    package AircraftSystemsATAs {
        part def AirConditioning;
        part def FlightControl;
        part def CabinSystem;
        part def CommunicationSystem;
        part def IntegratedCircuit;
    }
    part def Structure;
    package StructureATAs {
        part def Door;
        part def Fusalage;
        part def LandingGear;
        part def Wing;
    }
}
